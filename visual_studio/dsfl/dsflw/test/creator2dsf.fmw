FME workspace creator2dsf.fmw

Parameters:
- DestDataset_DSFLW2 = c:\temp\a.dsf   # DSFL Files(*.dsf)|*.dsf|All Files|*.* Destination DSFL File

Writers:
- DSFLW2_1: DSFLW2 to $(DestDataset_DSFLW2)

Creator
    GEOM = <?xml version="1.0" encoding="US_ASCII" standalone="no" ?><geometry><text><point><coord x="0" y="0"/></point><encodedTextString>Hello&lt;space&gt;&lt;u00e5&gt;&lt;u00e4&gt;&lt;u00f6&gt;&lt;space&gt;World!</encodedTextString><textSize>10</textSize><textRotation>20</textRotation></text></geometry>
    NUM = 1
    GEOMTYPE = Geometry Object
    CREATED -> AttributeExposer
AttributeExposer
    ATTR_LIST = fme_text_string
    -> AttributeCreator
AttributeCreator
    ATTR_LIST = dsfl_text_code,D5101,D5101,@Value(fme_text_string)
    -> Offsetter
    -> dsfl (writer DSFLW2_1)
Creator_2
    GEOM = <?xml version="1.0" encoding="US_ASCII" standalone="no" ?><geometry><line><coord x="2" y="3"/><coord x="4" y="6"/><coord x="4" y="8"/></line></geometry>
    NUM = 1
    GEOMTYPE = Geometry Object
    CREATED -> AttributeCreator_2
AttributeCreator_2
    ATTR_LIST = dsfl_class,K2,dsfl_subclass,U1
    -> Offsetter
    -> dsfl (writer DSFLW2_1)
Offsetter
    YOFF = 0
    ZOFF = 0
    XOFF = 20
    OFFSET -> dsfl (writer DSFLW2_1)
dsfl (writer DSFLW2_1)
    attributes: dsfl_type char(50)
