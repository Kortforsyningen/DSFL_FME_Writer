FME workspace aggregate.fmw

Parameters:
- SourceDataset_FFS = $(FME_MF_DIR)testdata\src\ffs\dsfl_aggregate.ffs   # Source FME Feature Store (FFS) File(s)
- DestDataset_DSFLW2 = c:\temp\aggregate.dsf   # DSFL Files(*.dsf)|*.dsf|All Files|*.* Destination DSFL File

Readers:
- FFS_1: FFS from $(SourceDataset_FFS)

Writers:
- DSFLW2_1: DSFLW2 to $(DestDataset_DSFLW2)

dsfl_header (reader FFS_1)
    attributes: H0 char(7), H1 char(4), H3 char(3), H4 char(15), H5 char(15), H11 char(17), H12 char(17), H13 number(5,0), H14 char(13), H15 number(9,0), H16 number(9,0), H41 number(11,0), H57 number(11,0), H58 char(57), H59 number(11,0), kms_feature_type char(12), kms_file_name char(15)
    -> AttributeCreator
dsfl_aggregate (reader FFS_1)
    attributes: D100 number(2,0), D111 number(4,0), D5601 char(11), D5602 number(6,0), dsfl_class char(3), dsfl_subclass char(3), kms_feature_type char(15), kms_file_name char(15)
    -> AttributeCreator
AttributeCreator
    ATTR_LIST = dsfl_type,@Value(kms_feature_type)
    -> dsfl (writer DSFLW2_1)
dsfl (writer DSFLW2_1)
    attributes: dsfl_type char(50)
