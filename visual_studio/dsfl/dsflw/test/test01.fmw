FME workspace test01.fmw

Parameters:
- SourceDataset_FFS = C:\Projekt\dsflw\svn\visual_studio\dsfl\dsflw\test\testdata\src\ffs\dsfl_polygon.ffs   # Source FME Feature Store (FFS) File(s)
- DestDataset_DSFLW = C:\Projekt\dsflw\svn\visual_studio\dsfl\dsflw\test\output\test01.dsf   # DSFL Files(*.dsf)|*.dsf|All Files|*.* Destination DSFL File

Readers:
- FFS_1: FFS from $(SourceDataset_FFS)

Writers:
- DSFLW_1: DSFLW to $(DestDataset_DSFLW)

Debugger
    DEBUG_OPTIONS_DIS = MAPPING_FILE
dsfl_header (reader FFS_1)
    attributes: H0 char(7), H1 char(5), H3 char(3), H4 char(23), H5 char(23), H11 char(25), H12 char(17), H13 number(5,0), H14 char(13), H15 number(9,0), H16 number(9,0), H41 char(12), H57 char(32), H58 char(67), H59 number(7,0), dsfl_type char(12), kms_feature_type char(12), kms_file_name char(9)
    -> AttributeRemover
Note: Removing H12 here so that value / from directive is used instead
AttributeRemover
    REMOVE_ATTRS = H12
    -> TclCaller
dsfl_origin (reader FFS_1)
    attributes: dsfl_origin_ND51 char(35), dsfl_origin_ND53 char(24), dsfl_origin_ND54 char(27), dsfl_origin_ND55 char(28), dsfl_origin_record_index number(9,0), dsfl_type char(10), kms_feature_type char(12), kms_file_name char(9)
    -> TclCaller
dsfl_aggregate (reader FFS_1)
    attributes: D5001 number(6,0), D5002 char(19), D5703 number(6,0), D5710 number(8,0), D5711 number(5,0), D5712 char(30), D5720 number(8,0), D5732 char(7), D5738 number(9,0), D5759 char(27), D50051 char(6), dsfl_class char(4), dsfl_origin_record_index number(9,0), dsfl_subclass char(4), dsfl_type char(13), kms_feature_type char(15), kms_file_name char(9)
    -> TclCaller
dsfl_point (reader FFS_1)
    attributes: D592 char(2), D597 char(79), D5001 number(6,0), D5010 char(12), D5101 char(11), D5450 char(3), D5710 number(10,0), D5711 number(5,0), D5712 char(23), D5721 number(10,0), D5735 char(12), D5736 number(2,0), D5737 char(3), D5738 number(9,0), D5756 number(10,0), D5759 char(31), D5942 number(11,3), D5943 number(10,3), D5944 number(5,0), D51011 number(7,0), dsfl_class char(4), dsfl_origin_record_index number(9,0), dsfl_point_rotation number(2,0), dsfl_subclass char(5), dsfl_type char(11), kms_feature_type char(11), kms_file_name char(9)
    -> TclCaller
dsfl_line (reader FFS_1)
    attributes: D5001 number(6,0), D5002 char(19), D5010 char(12), D5710 number(10,0), D5711 number(5,0), D5712 char(27), D5716 char(28), D5718 number(10,0), D5719 number(10,0), D5720 number(10,0), D5721 number(10,0), D5734 number(9,0), D5735 char(12), D5737 char(3), D5738 number(9,0), D5749 number(10,0), D5751 number(10,0), D5757 number(10,0), D5759 char(28), D5763 char(6), D5765 number(10,0), D50051 char(4), dsfl_class char(4), dsfl_origin_record_index number(9,0), dsfl_subclass char(6), dsfl_type char(10), kms_feature_type char(10), kms_file_name char(9)
    -> TclCaller
dsfl_text (reader FFS_1)
    attributes: D111 number(5,0), D597 char(79), D5001 number(6,0), D5002 char(19), D5010 char(13), D5031 char(6), D5034 char(9), D5101 char(11), D5710 number(10,0), D5711 number(5,0), D5712 char(31), D5720 number(10,0), D5721 number(10,0), D5722 char(23), D5738 number(9,0), D5744 number(9,0), D5759 char(28), D5944 number(5,0), D50051 char(6), D50053 char(4), D50091 char(4), D50093 char(4), D51011 number(7,0), dsfl_origin_record_index number(9,0), dsfl_rotation number(18,14), dsfl_text_code char(7), dsfl_text_justification char(19), dsfl_text_value char(11), dsfl_type char(10), kms_feature_type char(10),
      kms_file_name char(9)
    -> TclCaller
dsfl_polygon (reader FFS_1)
    attributes: D111 number(5,0), D5001 number(6,0), D5002 char(19), D5010 char(13), D5703 number(6,0), D5704 char(2), D5708 number(11,0), D5709 char(4), D5710 number(10,0), D5720 number(8,0), D5721 number(10,0), D5722 char(23), D5727 number(8,0), D5732 char(7), D5734 number(9,0), D5738 number(9,0), D5739 number(6,0), D5740 number(5,0), D5741 char(19), D5742 number(5,0), D5743 char(17), D5745 number(10,0), D5746 char(13), D5748 number(10,0), D5750 number(10,0), D5754 char(7), D5756 number(10,0), D5759 char(29), D5760 char(7), D5761 number(6,0),
      D5762 char(2), D50031 number(5,0), D50051 char(6), D50091 char(4), dsfl_class char(4), dsfl_origin_record_index number(5,0), dsfl_subclass char(4), dsfl_type char(13), kms_feature_type char(13), kms_file_name char(9)
    -> TclCaller
Note: Should be implemented / in writer instead
TclCaller
    VAL_ATTR = _result
    TCLPROG = formatText
    SRC:
      proc formatText {} {

           foreach attr [ lsearch -inline -all -regexp [ FME_AttributeNames ] {^D[0-9]+$|_ND[0-9]+$} ] {
              set s [ FME_GetAttribute $attr ]
              if { ! [regexp -- {^[0-9.]+$|^$} $s ] } {
                     FME_SetAttribute $attr [format {"%s"}  [regsub -all {["]} $s  {""}] ]
                 }
           }
           return
      }
    -> CoordinateSwapper
Note: Not clear where this should be done, should maybe be that writer parameter setting
CoordinateSwapper
    SWAP_TYPE = X <-> Y
    -> NewFeatureType (writer DSFLW_1)
NewFeatureType (writer DSFLW_1)
