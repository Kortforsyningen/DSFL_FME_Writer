FME workspace minimaks.fmw

Parameters:
- SourceDataset_FFS = $(FME_MF_DIR)testdata\src\ffs\minimaks.ffs   # Source FME Feature Store (FFS) File(s)
- FEATURE_TYPES =

Readers:
- FFS_1: FFS from $(SourceDataset_FFS)

dsfl_line (reader FFS_1)
    attributes: D5001 number(6,0), D5002 char(19), D5010 char(12), D5710 number(10,0), D5711 number(5,0), D5712 char(27), D5716 char(28), D5718 number(10,0), D5719 number(10,0), D5720 number(10,0), D5721 number(10,0), D5734 number(9,0), D5735 char(12), D5737 char(3), D5738 number(9,0), D5749 number(10,0), D5751 number(10,0), D5757 number(10,0), D5759 char(28), D5763 char(6), D5765 number(10,0), D50051 char(4), dsfl_class char(4), dsfl_origin_record_index number(9,0), dsfl_subclass char(6), dsfl_type char(10), kms_feature_type char(10), kms_file_name char(9), D5746 char(13), D111 number(5,0),
      H0 char(7), D5732 char(7), H12 char(17), D5704 char(2), dsfl_origin_ND53 char(24), H5 char(23), D5750 number(10,0), dsfl_text_justification char(19), D50031 number(5,0), dsfl_origin_ND51 char(35), dsfl_text_value char(11), H14 char(13), D5703 number(6,0), H41 char(12), D5031 char(6), D50053 char(4), D5034 char(9), D50091 char(4), D5744 number(9,0), D5745 number(10,0), D5727 number(8,0), H1 char(5), H13 number(5,0), H11 char(25), dsfl_origin_ND55 char(28), D5101 char(11), dsfl_origin_ND54 char(27), dsfl_text_code char(7), D5743 char(17), D5761 number(6,0),
      D5762 char(2), D5756 number(10,0), H16 number(9,0), D5708 number(11,0), H4 char(23), D5741 char(19), D5760 char(7), H3 char(3), H58 char(67), H59 number(7,0), D597 char(79), D5748 number(10,0), D5742 number(5,0), D5739 number(6,0), D5740 number(5,0), D5944 number(5,0), H57 char(32), D51011 number(7,0), D50093 char(4), D5709 char(4), dsfl_rotation number(18,14), H15 number(9,0), D5722 char(23), D5754 char(7)
    -> GeometryFilter
GeometryFilter
    BREAK_AGG = No
    NULL -> AttributeCreator
    POINT -> Sampler
    LINE -> Sampler
    AREA -> Sampler
AttributeCreator
    ATTR_LIST = dsfl_type,@Value(kms_feature_type)
    -> Sampler
Sampler
    RATE = 1
    SAMPLE_TYPE_LONG = Every Nth Feature
